(defun c:zp()
(command "._zoom" "_P")
      )


(defun c:za()
(command "._zoom" "_a")
      )

(defun c:ze()
(command "._zoom" "_e")
      )

(defun c:zo()
(command "._zoom" "_o")
      )

(defun c:zw()
(command "._zoom" "_w")
      )
